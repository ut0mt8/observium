-- ===================================================================
-- == Copyright (C) 2004 Paradyne Corporation.                      ==
-- ===================================================================

PDN-PPP-BRIDGE-NCP-EXT-MIB DEFINITIONS ::= BEGIN

IMPORTS
   MODULE-IDENTITY, OBJECT-TYPE
      FROM SNMPv2-SMI
   OBJECT-GROUP, MODULE-COMPLIANCE
      FROM SNMPv2-CONF
   pppBridgeEntry, pppBridgeMediaConfigEntry
      FROM PPP-BRIDGE-NCP-MIB
   SwitchState, PdnPPPState
      FROM PDN-TC
   pdn-interfaces
      FROM PDN-HEADER-MIB;
        
pdnPppBridgeExtMIB MODULE-IDENTITY
   LAST-UPDATED "200409100000Z"  -- September 10, 2004
   ORGANIZATION "Paradyne Networks
                 MIB Working Group
                 Other information about group editing the MIB"
   CONTACT-INFO "Paradyne Networks, Inc.
                 8545 126th Avenue North
                 Largo, FL 33733
                 www.paradyne.com
        
                 General Comments to: mibwg_team@paradyne.com

                 Editor
                    Clay Sikes"

   DESCRIPTION  "The MIB module provides enterprise-specific extensions
                 to the PPP-BRIDGE-MIB for managing the Bridge Control
                 Protocol (BCP) on subnetwork interfaces that use the 
                 family of point-to-Point Protocols (PPP).  BCP is a 
                 member of the Network Control Protocol suite of 
                 point-to-point protocols.

                 The following documents should be referenced with 
                 respect to this MIB module:
                 [RFC 1474]    Kastenholz, F., `The Definitions of 
                               Managed Objects for the Bridge Network 
                               Control Protocol of the Point-to-Point 
                               Protocol', June 1993.
                 [RFC 1661]    Simpson, W., `The Point-to-Point 
                               Protocol', July 1994.
                 [RFC 3518]    Higashiyama, M., Baker, F., and Liao, T.,
                               `Point-to-Point Protocol (PPP) Bridging 
                               Control Protocol (BCP)', April 2003."

   REVISION     "200409100000Z"  -- September 10, 2004
   DESCRIPTION  "Initial release."

::=  { pdn-interfaces 29 }



-- ====================================================================
-- == Define groups for Notifications, MIB Objects, Accessible for   ==
-- == Notifications (AFNs), and Conformance.                         ==
-- == These may just be place holders.                               ==
-- ====================================================================
pdnPppBridgeExtNotifications OBJECT IDENTIFIER ::= 
   { pdnPppBridgeExtMIB 0 }
pdnPppBridgeExtObjects       OBJECT IDENTIFIER ::= 
   { pdnPppBridgeExtMIB 1 }
pdnPppBridgeExtAFNs          OBJECT IDENTIFIER ::= 
   { pdnPppBridgeExtMIB 2 } 
pdnPppBridgeExtConformance   OBJECT IDENTIFIER ::= 
   { pdnPppBridgeExtMIB 3 }




-- ====================================================================
-- ==                  Textual Conventions                           ==
-- ====================================================================
-- None defined.



-- ====================================================================
-- ==                  MIB Objects                                   ==
-- ====================================================================




-- ===================================================================
-- == pdnPppBridgeExtTable                                          ==
-- ===================================================================
pdnPppBridgeExtTable  OBJECT-TYPE
   SYNTAX      SEQUENCE OF PdnPppBridgeExtEntry
   MAX-ACCESS  not-accessible
   STATUS      current
   DESCRIPTION "An entry in the PPP Bridge Table, pppBridgeTable.
                The PPP Bridge Table contains parameters and 
                statistics for the local PPP entity."
   ::= { pdnPppBridgeExtObjects 1 }

pdnPppBridgeExtEntry  OBJECT-TYPE
   SYNTAX      PdnPppBridgeExtEntry
   MAX-ACCESS  not-accessible
   STATUS      current
   DESCRIPTION "An entry in the Multilink PPP Configuration Table."
   AUGMENTS    { pppBridgeEntry }
   ::= { pdnPppBridgeExtTable 1 }

PdnPppBridgeExtEntry ::=
   SEQUENCE {
      pdnPppBridgeBcpLinkStatusCurrState     PdnPPPState,
      pdnPppBridgeLocalToRemote802Tagged     SwitchState,
      pdnPppBridgeRemoteToLocal802Tagged     SwitchState        
   }

pdnPppBridgeBcpLinkStatusCurrState OBJECT-TYPE
   SYNTAX      PdnPPPState
   MAX-ACCESS  read-only
   STATUS      current
   DESCRIPTION "The current state of the BCP State Machine."
   REFERENCE   "RFC 1661, Section 4.2, `State Transition Table'."
   ::= { pdnPppBridgeExtEntry 1 }

pdnPppBridgeLocalToRemote802Tagged  OBJECT-TYPE
   SYNTAX      SwitchState
   MAX-ACCESS  read-only
   STATUS      current
   DESCRIPTION "Indicates whether or not the local PPP entity is 
                transmitting IEEE 802 tagged frames.  An enabled(1) 
                indicates that frames will be transmitted 802 tagged.
                A disabled(2) indicate that frames will not be 
                transmitted 802 tagged."
   REFERENCE    "RFC 3518, Section 5.7, `IEEE-802-Tagged-Frame'."
   ::= { pdnPppBridgeExtEntry 2 }

pdnPppBridgeRemoteToLocal802Tagged  OBJECT-TYPE
   SYNTAX      SwitchState
   MAX-ACCESS  read-only
   STATUS      current
   DESCRIPTION "Indicates whether or not the remote PPP entity is 
                transmitting IEEE 802 tagged frames.  An enabled(1) 
                indicates that frames will be transmitted 802 tagged.
                A disabled(2) indicate that frames will not be 
                transmitted 802 tagged."
   REFERENCE    "RFC 3518, Section 5.7, `IEEE-802-Tagged-Frame'."
   ::= { pdnPppBridgeExtEntry 3 }



-- ===================================================================
-- == pdnPppBridgeMediaConfigExtTable                               ==
-- ===================================================================
pdnPppBridgeMediaConfigExtTable  OBJECT-TYPE
   SYNTAX      SEQUENCE OF PdnPppBridgeMediaConfigExtEntry
   MAX-ACCESS  not-accessible
   STATUS      current
   DESCRIPTION "An entry in the PPP Bridge Media Configuration Table,
                pppBridgeTable.  The PPP Bridge Media Configuration 
                Table contains objects relative to MAC media types."
   ::= { pdnPppBridgeExtObjects 2 }

pdnPppBridgeMediaConfigExtEntry  OBJECT-TYPE
   SYNTAX      PdnPppBridgeMediaConfigExtEntry
   MAX-ACCESS  not-accessible
   STATUS      current
   DESCRIPTION "An entry in the Multilink PPP Media Configuration 
                Table."
   AUGMENTS    { pppBridgeMediaConfigEntry }
   ::= { pdnPppBridgeMediaConfigExtTable 1 }

PdnPppBridgeMediaConfigExtEntry ::=
   SEQUENCE {
      pdnPppBridgeMediaIeee802Tagged     SwitchState
   }

pdnPppBridgeMediaIeee802Tagged OBJECT-TYPE
   SYNTAX      SwitchState
   MAX-ACCESS  read-write
   STATUS      current
   DESCRIPTION "Configures whether or not the local PPP entity will
                attempt to negotiate the IEEE-802-Tagged Frame option.
                An enabled(1) will result in the option being 
                supported.  A disabled(2) will result in the options
                not being supported."
   REFERENCE   "RFC 3518, Section 5.7, `IEEE-802-Tagged-Frame'."
   ::= { pdnPppBridgeMediaConfigExtEntry 1 }



-- ====================================================================
-- ==                  Accessible for Notifications (AFNs)           ==
-- ====================================================================
-- None defined



-- ===================================================================
-- ==                  Traps/Notifications                          ==
-- ===================================================================
-- None defined



-- ====================================================================
-- ==                  Conformance Information                       ==
-- ====================================================================

pdnPppBridgeExtCompliances  OBJECT IDENTIFIER ::= 
   { pdnPppBridgeExtConformance 1 }
pdnPppBridgeExtGroups       OBJECT IDENTIFIER ::= 
   { pdnPppBridgeExtConformance 2 }


-- ===========================
-- == Compliance Statements ==
-- ===========================


pdnPppBridgeExtCompliance  MODULE-COMPLIANCE
   STATUS      current
   DESCRIPTION "The compliance statement for network elements 
                implementing PPP Bridging Control Protocol."
   MODULE      -- this module
   -- No mandatory groups are specified.  PPP BRIDGE NCP can be 
   -- implemented with only object defined in 
   -- the PPP-BRIDGE-NCP-MIB.  However, this MIB module specifies
   -- optional objects to enhance a PPP BRIDGE NCP implementation.
   
   GROUP       pdnPppBridgeExtStateMachineGroup
   DESCRIPTION "This group is only required for implementations that
                need to display the BCP State Machine's state."

   GROUP       pdnPppBridgeExt802TaggedGroup
   DESCRIPTION "This group is only required for implementations that
                need to display whether or not IEEE 802 tagged frames
                are being transmitted."

    ::= { pdnPppBridgeExtCompliances 1 }


-- ==========================
-- == Units of Conformance ==
-- ==========================

pdnPppBridgeExtObjGroups   OBJECT IDENTIFIER ::= 
   { pdnPppBridgeExtGroups 1 }
pdnPppBridgeExtAfnGroups   OBJECT IDENTIFIER ::= 
   { pdnPppBridgeExtGroups 2 }
pdnPppBridgeExtNtfyGroups  OBJECT IDENTIFIER ::= 
   { pdnPppBridgeExtGroups 3 }


-- ===================
-- == Object Groups ==
-- ===================


pdnPppBridgeExtStateMachineGroup OBJECT-GROUP
   OBJECTS {
      pdnPppBridgeBcpLinkStatusCurrState
   }
   STATUS      current
   DESCRIPTION "Displays the BCP State Machine's state."
   ::= { pdnPppBridgeExtObjGroups 1 }

pdnPppBridgeExt802TaggedGroup OBJECT-GROUP
   OBJECTS {
       pdnPppBridgeMediaIeee802Tagged,
       pdnPppBridgeLocalToRemote802Tagged,
       pdnPppBridgeRemoteToLocal802Tagged
   }
   STATUS      current
   DESCRIPTION "Displays whether or not IEEE 802 tagged frames
                are being transmitted."
   ::= { pdnPppBridgeExtObjGroups 2 }



-- =========================================
-- == Accessible for Notifications Groups ==
-- =========================================
-- None defined



-- =========================
-- == Notification Groups ==
-- =========================
-- None defined




-- =========
-- == END ==
-- =========
END
