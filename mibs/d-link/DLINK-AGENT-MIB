-- Revision 1.87 Draft ***************************
-- Description:
-- [New Object]
-- Add agentStatusReset, agentReboot and agentReset.
-- Deprecated agentSystemReset
-- Notes: Created for follow CLI spec.
-- Revision 1.86 Draft ***************************
-- 2007/01/17 05:15下午
-- Add object 'agentTrustHostIPSubnetMask ' in agentTrustHostTable
-- Revision 1.85 Draft ***************************
-- 2006/10/17 01:45下午
-- Add group 'agentTrustHostMgmt'
-- Revision 1.84 Draft ***************************
-- 2006/5/19 01:45下午
-- Add group 'agentPORTutilizationTable'
-- Revision 1.83 Draft ***************************
-- 2004/1/12 11:50上午  ***************************
-- Add a object 'agentBscSwFileBIncrement' in agentBscSwFileTable
-- Add group 'agentCPUutilization'
-- Add swMultiImageCtrlTable ,swMultiImageInfoTable
-- Revision 1.82 Draft ***************************
--2003/5/14 02:11下午  ***************************
-- re-arrange the agentNotify subtree
-- ************************************************************************
-- Revision 1.81 Draft ***************************
-- 2003/3/24 03:09下午
-- remove  status "changed-not-save(4)"  in object agentStatusSaveCfg
-- change object  MAX-ACCESS of agentTrapManagerIpAddr  from read-only to read-write
-- ************************************************************************
-- Revision 1.8 Draft ***************************
-- 2003/1/21 11:21上午
-- Modified  Common traps and management
-- **********************************************
-- Remove agentConsoleModeManager , agentSlipModeManager
-- Add Common traps management
-- Revision 1.7
-- Copyright 2000 D-Link Inc.
-- All rights reserved.

DLINK-AGENT-MIB  DEFINITIONS ::= BEGIN

    IMPORTS
        IpAddress			        FROM RFC1155-SMI
        MODULE-IDENTITY, OBJECT-TYPE,
        Integer32		 	FROM SNMPv2-SMI
        TruthValue          FROM SNMPv2-TC
        DisplayString		FROM RFC1213-MIB
        AgentNotifyLevel    FROM DLINK-ID-REC-MIB
        RowStatus           	FROM SNMPv2-TC
        dlink-common-mgmt	FROM DLINK-ID-REC-MIB;

      agentGeneralMgmt MODULE-IDENTITY
	    LAST-UPDATED "0007150000Z"
	    ORGANIZATION "D-Link, Inc."
	    CONTACT-INFO
	        "   D-Link Customer Service

		    Postal: No. 20,Park Ave, II, Science-based
			        Industrial Park, Hsinchu, taiwan, R.O.C.

		       Tel: 886-3-577-9966

		    E-mail: "
	    DESCRIPTION
		    "The Structure of Common Management Information for the
		    D-Link enterprise."
        ::= {  dlink-common-mgmt 1 }

    -- ****************
    -- agentBasicInfo *
    -- ****************
    agentBasicInfo          OBJECT IDENTIFIER ::= { agentGeneralMgmt 1 }

    agentMgmtProtocolCapability OBJECT-TYPE
        SYNTAX  INTEGER {
                    other(1),
                    snmp-ip(2),
                    snmp-ipx(3),
                    snmp-ip-ipx(4)
                }
        MAX-ACCESS  read-only
        STATUS  current
        DESCRIPTION
            "The network management protocol(s) supported by this agent."
        ::= { agentBasicInfo 1 }


    -- *************************
    -- agentMibcapabilityTable *
    -- *************************

    agentMibCapabilityTable OBJECT-TYPE
        SYNTAX  SEQUENCE OF AgentMibCapabilityEntry
        MAX-ACCESS  not-accessible
        STATUS  current
        DESCRIPTION
            "A list of MIB capability entries supported by this agent."
        ::= { agentBasicInfo 2 }

    agentMibCapabilityEntry OBJECT-TYPE
        SYNTAX  AgentMibCapabilityEntry
        MAX-ACCESS  not-accessible
        STATUS  current
        DESCRIPTION
            "A MIB capability entry contains objects describing a particular MIB
             supported by this agent."
        INDEX   { agentMibCapabilityIndex }
        ::= { agentMibCapabilityTable 1 }

    AgentMibCapabilityEntry ::=
        SEQUENCE {
            agentMibCapabilityIndex
                Integer32,
            agentMibCapabilityDescr
                DisplayString,
            agentMibCapabilityVersion
                Integer32,
            agentMibCapabilityType
                INTEGER
        }

    agentMibCapabilityIndex OBJECT-TYPE
        SYNTAX  Integer32
        MAX-ACCESS  read-only
        STATUS  current
        DESCRIPTION
            "A list of agentMibCapabilityDescr entries."
        ::= { agentMibCapabilityEntry 1 }

    agentMibCapabilityDescr OBJECT-TYPE
        SYNTAX  DisplayString (SIZE (0..35))
        MAX-ACCESS  read-only
        STATUS  current
        DESCRIPTION
            "The name of the MIB supported by the agent."
        ::= { agentMibCapabilityEntry 2 }

    agentMibCapabilityVersion OBJECT-TYPE
        SYNTAX  Integer32
        MAX-ACCESS  read-only
        STATUS  current
        DESCRIPTION
            "The version of the MIB specified in this entry."
        ::= { agentMibCapabilityEntry 3 }

    agentMibCapabilityType OBJECT-TYPE
        SYNTAX  INTEGER {
                    other(1),
                    standard(2),
                    proprietary(3),
                    experiment(4)
                }
        MAX-ACCESS  read-only
        STATUS  current
        DESCRIPTION
            "The type of the MIB specified in this entry."
        ::= { agentMibCapabilityEntry 4 }


    agentStatusConsoleInUse   OBJECT-TYPE
        SYNTAX INTEGER {
               other(1),
               in-use(2),
               not-in-use(3)
               }
        MAX-ACCESS read-only
        STATUS current
        DESCRIPTION
            "This indicates whether console is currently in-use."
        ::= { agentBasicInfo 3 }

    agentStatusSaveCfg OBJECT-TYPE
        SYNTAX INTEGER {
               other(1),
               proceeding(2),
               completed(3),
               failed(4)
               }
        MAX-ACCESS read-only
        STATUS current
        DESCRIPTION
            "This indicates the status of the device configuration.

            other(1) - this entry is currently in use but the conditions
                     under which it will remain so are different from each
                     of the following values.
            proceeding(2) - the device configuration is being currently saved into the NV-RAM.
            completed(3) – all of the device configuration parameters have been
                     saved into NV-RAM.
            failed(4) - The process to save device configuration has failed."
        ::= { agentBasicInfo 4 }

    agentStatusFileTransfer OBJECT-TYPE
        SYNTAX  INTEGER {
                    other(1) ,
                    in-process(2),
                    invalid-file(3),
                    violation(4),
                    file-not-found(5),
                    disk-full(6),
                    complete(7),
                    time-out(8),
                    not-format(9),
                    memory-full(10)
                }
        MAX-ACCESS  read-only
        STATUS  current
        DESCRIPTION
            "status of firmware download control. If the value is 'other',
            means never firmware updated since device started up."
        ::= { agentBasicInfo 5 }

    -- *************************
    -- agentCPUutilizationTable *
    -- *************************
    agentCPUutilization          OBJECT IDENTIFIER ::= { agentBasicInfo 6 }


    agentCPUutilizationIn5sec OBJECT-TYPE
        SYNTAX  Integer32
        MAX-ACCESS  read-only
        STATUS  current
        DESCRIPTION
            "Time scale is 5 seconds.The value will be between 0%(idle) and 100%
            (very busy)."
        ::= { agentCPUutilization 1 }

    agentCPUutilizationIn1min OBJECT-TYPE
        SYNTAX  Integer32

        MAX-ACCESS  read-only
        STATUS  current
        DESCRIPTION
            "Time scale is 1 minute.The value will be between 0%(idle) and 100%
            (very busy)."
        ::= { agentCPUutilization 2 }

    agentCPUutilizationIn5min OBJECT-TYPE
        SYNTAX  Integer32
        MAX-ACCESS  read-only
        STATUS  current
        DESCRIPTION
            "Time scale is 5 minute.The value will be between 0%(idle) and 100%
            (very busy)."
        ::= { agentCPUutilization 3 }

    -- *************************
    -- agentPORTutilizationTable *
    -- *************************
    agentPORTutilizationTable OBJECT-TYPE
        SYNTAX  SEQUENCE OF AgentPORTutilizationEntry
        MAX-ACCESS  not-accessible
        STATUS  current
        DESCRIPTION
            "The table specifies port's utilization function."
        ::= { agentBasicInfo 7 }

    agentPORTutilizationEntry OBJECT-TYPE
        SYNTAX  AgentPORTutilizationEntry
        MAX-ACCESS  not-accessible
        STATUS  current
        DESCRIPTION
            "A list of information about port's utilization function."
        INDEX   { agentPORTutilizationProtIndex }
        ::= { agentPORTutilizationTable 1 }

    AgentPORTutilizationEntry ::=
        SEQUENCE {
            agentPORTutilizationProtIndex
                INTEGER,
            agentPORTutilizationTX
                INTEGER,
            agentPORTutilizationRX
                INTEGER,
            agentPORTutilizationUtil
                INTEGER
        }

    agentPORTutilizationProtIndex OBJECT-TYPE
        SYNTAX  INTEGER (1..65535)
        MAX-ACCESS  read-only
        STATUS  current
        DESCRIPTION
            "This object indicates the module's port number."
        ::= { agentPORTutilizationEntry 1 }

    agentPORTutilizationTX OBJECT-TYPE
        SYNTAX  INTEGER
        MAX-ACCESS  read-only
        STATUS  current
        DESCRIPTION
            "The real time gauges of transmitted frames on the specific port."
        ::= { agentPORTutilizationEntry 2 }

    agentPORTutilizationRX OBJECT-TYPE
        SYNTAX  INTEGER
        MAX-ACCESS  read-only
        STATUS  current
        DESCRIPTION
            "The real time gauges of recieved frames on the specific port."
        ::= { agentPORTutilizationEntry 3 }

    agentPORTutilizationUtil OBJECT-TYPE
        SYNTAX  INTEGER (0..100)
        UNITS       "%"
        MAX-ACCESS  read-only
        STATUS  current
        DESCRIPTION
            "The real time percentage of the port statistics."
        ::= { agentPORTutilizationEntry 4 }

-- -----------------------------------------------------------------------------
    agentDRAMutilizationTable OBJECT-TYPE
        SYNTAX  SEQUENCE OF AgentDRAMutilizationEntry
        MAX-ACCESS not-accessible
        STATUS  current
        DESCRIPTION
             "Information about DRAM memory."
        ::={agentBasicInfo 9}

     agentDRAMutilizationEntry OBJECT-TYPE
        SYNTAX   AgentDRAMutilizationEntry
        MAX-ACCESS not-accessible
        STATUS   current
        DESCRIPTION
            "A list of information about DRAM memory."
        INDEX {agentDRAMutilizationUnitID}
        ::={agentDRAMutilizationTable 1}

     AgentDRAMutilizationEntry ::=
        SEQUENCE {
                agentDRAMutilizationUnitID
                         INTEGER,
                agentDRAMutilizationTotalDRAM
                         INTEGER,
                agentDRAMutilizationUsedDRAM
                         INTEGER,
                agentDRAMutilization
                         INTEGER
                 }

     agentDRAMutilizationUnitID OBJECT-TYPE
        SYNTAX  INTEGER
        MAX-ACCESS read-only
        STATUS  current
        DESCRIPTION
             "Specifies the unit ID.
              If the ID equals to zero, it means the current device."
        ::={ agentDRAMutilizationEntry 1 }

     agentDRAMutilizationTotalDRAM OBJECT-TYPE
        SYNTAX  INTEGER
        UNITS	"KB"
        MAX-ACCESS read-only
        STATUS current
        DESCRIPTION
            "The size of Total DRAM Memory."
        ::={agentDRAMutilizationEntry 2}

     agentDRAMutilizationUsedDRAM OBJECT-TYPE
        SYNTAX  INTEGER
        UNITS	"KB"
        MAX-ACCESS read-only
        STATUS current
        DESCRIPTION
            "The size of used DRAM memory."
        ::={agentDRAMutilizationEntry 3}

     agentDRAMutilization OBJECT-TYPE
        SYNTAX  INTEGER
        MAX-ACCESS read-only
        STATUS  current
        DESCRIPTION
             "The percentage of used DRAM memory of the total DRAM memory available.
              The value will be between 0%(idle) and 100%(very busy)."
        ::={agentDRAMutilizationEntry 4}

-- -----------------------------------------------------------------------------
	agentStatusReset OBJECT-TYPE
        SYNTAX INTEGER {
               proceeding(1),
               completed(2),
               failed(3)
               }
        MAX-ACCESS  read-only
        STATUS      current
        DESCRIPTION
            "This indicates the status of 'agentReset'."
        ::= { agentBasicInfo 11 }


    -- ******************
    -- agentBasicConfig *
    -- ******************
    agentBasicConfig        OBJECT IDENTIFIER ::= { agentGeneralMgmt 2 }

    agentBscSwFileTable OBJECT-TYPE
        SYNTAX  SEQUENCE OF AgentBscSwFileEntry
        MAX-ACCESS  not-accessible
        STATUS  current
        DESCRIPTION
            "A list of MIB Basic Config entries supported file Update by this agent."
        ::= { agentBasicConfig 1 }

    agentBscSwFileEntry OBJECT-TYPE
        SYNTAX  AgentBscSwFileEntry
        MAX-ACCESS  not-accessible
        STATUS  current
        DESCRIPTION
            "A basic configuration entry contains objects describing a particular MIB
             supported by this agent."
        INDEX   { agentBscSwFileIndex }
        ::= { agentBscSwFileTable 1 }

    AgentBscSwFileEntry ::=
    	SEQUENCE {
    		agentBscSwFileIndex
    			Integer32,
    		agentBscSwFileDscr
    			DisplayString,
    		agentBscSwFileAddr
    			IpAddress,
    		agentBscSwFileTransferType
    			INTEGER,
        	agentBscSwFile
        		DisplayString,
        	agentBscSwFileLocateId
        		INTEGER,
        	agentBscSwFileLoadType
        		INTEGER,
        	agentBscSwFileCtrl
        		INTEGER,
        	agentBscSwFileBIncrement
        	    TruthValue,
        	agentMultiImageCtrlID
        		INTEGER

        }

    agentBscSwFileIndex OBJECT-TYPE
    	SYNTAX	Integer32
    	MAX-ACCESS	read-only
    	STATUS	current
    	DESCRIPTION
    		"The table index for the file entry"
    	::= { agentBscSwFileEntry 1 }

    agentBscSwFileDscr OBJECT-TYPE
        SYNTAX  DisplayString  (SIZE (0..64))
        MAX-ACCESS  read-write
        STATUS  current
        DESCRIPTION
            "The description for the purpose of the software file in this entry.
			 Note:
			 For systems which do not support change of this object, setting values to
			 this object will cause the system to return bad-value error message.
			 "
        ::= { agentBscSwFileEntry 2 }

    agentBscSwFileAddr OBJECT-TYPE
        SYNTAX  IpAddress
        MAX-ACCESS  read-write
        STATUS  current
        DESCRIPTION
            "The IP address where the file to be downloaded is located, or the IP address
            where the file will be uploaded to."
        ::= {  agentBscSwFileEntry 3 }

    agentBscSwFileTransferType OBJECT-TYPE
        SYNTAX  INTEGER {
                    other(1),
                    network-load(2),
                    out-of-band-load(3)
                }
        MAX-ACCESS  read-write
        STATUS  current
        DESCRIPTION
            "The channel through which the file will be downloaded or uploaded.

			 Note:
			 For systems which do not support all channels, setting values to the unsupported
			 channel will cause the system to return bad-value error message.
			 "
        ::= { agentBscSwFileEntry 4 }

    agentBscSwFile OBJECT-TYPE
        SYNTAX  DisplayString  (SIZE (0..64))
        MAX-ACCESS  read-write
        STATUS  current
        DESCRIPTION
            "The name of the file to be downloaded from the TFTP server, or to be uploaded
            to."
        ::= { agentBscSwFileEntry 5 }

     agentBscSwFileLocateId OBJECT-TYPE
        SYNTAX  INTEGER (1..16)
        MAX-ACCESS  read-write
        STATUS  current
        DESCRIPTION
            "This object describes the type of the file.
             runtime-code(1),
             log-file(2),
             cfg-file(3)

			 Note:
			 For system which does not support change of this object, setting value to
			 this object will cause the system to return bad-value error message.
             "
        ::= { agentBscSwFileEntry 6 }

     agentBscSwFileLoadType OBJECT-TYPE
        SYNTAX  INTEGER {
                    other(1),
                    upload(2),
                    download(3)
                }
        MAX-ACCESS  read-write
        STATUS  current
        DESCRIPTION
        	"This object allows the user to select download or upload function for the file.

			 Note:
			 For system which does not support change of this object, setting value to
			 this object will cause the system to return bad-value error message.
			 "
        ::= { agentBscSwFileEntry 7 }

     agentBscSwFileCtrl OBJECT-TYPE
        SYNTAX  INTEGER {
                    other(1),
                    inactive(2),
                    start(3),
                    delete(4),
                    config-as-bootup-fw(5)
                }
        MAX-ACCESS  read-write
        STATUS  current
        DESCRIPTION
            "This object allows the user to download runtime software. The setting
 		  	 will take effect when the system restarts. See Note(1) below

			 Note:
			 For systems which do not support change of this object to some value,
			 setting these values cause the system to return bad-value error messages.

			start - start to action.
	        delete(4) - delete the firmware by indicated firmware ID.
	        config-as-bootup-fw(5) - configured as bootup firmware by indicated
            firmware(ID)."
        ::= { agentBscSwFileEntry 8 }

	agentBscSwFileBIncrement OBJECT-TYPE
        SYNTAX     TruthValue
        MAX-ACCESS read-write
        STATUS current
        DESCRIPTION
            "The object indicates that whether the previous configuration will be valid
              or not after downloading the configuration file.
             True : keep valid
             False : erase. "
        ::= { agentBscSwFileEntry 9 }

    agentMultiImageCtrlID OBJECT-TYPE
        SYNTAX  INTEGER
        MAX-ACCESS  read-write
        STATUS  current
        DESCRIPTION
            "The section ID of firmware image."
        ::= { agentBscSwFileEntry 10 }

	agentFileTransfer OBJECT-TYPE
		SYNTAX INTEGER {
				other(1),
				start(2),
				start-and-reset(3),
				noaction(4)
			}
		MAX-ACCESS read-write
		STATUS obsolete
		DESCRIPTION
			"This object will execute the download or upload action. If start(2), it will
			begin to download/upload, but no reset follows. If start-and-reset(3), then
			the reset will activate after download or upload. No action if(4).

			 Note:
			 Because these functions will be limited by the system support, some of the
			 selected items will be invalid. When the user selects one of the items,
			 it will respond with bad-value status."
		::= { agentBasicConfig 2 }

    agentSystemReset OBJECT-TYPE
        SYNTAX  INTEGER {
                    other(1),
                    cold-start(2),
                    warm-start(3),
                    no-reset(4)
                }
        MAX-ACCESS  read-write
        STATUS      deprecated
        DESCRIPTION
            "This object indicates the agent system reset state. Setting this
             object to no-reset(4) has no effect. Setting this object to
             cold-start(2) or warm-start(3) will reset the agent. The agent
             always returns no-reset(4) when this object is read."
        ::= { agentBasicConfig 3 }

    agentRs232PortConfig OBJECT-TYPE
        SYNTAX  INTEGER  {
                    other(1),
                    console(2),
                    out-of-band(3),
					notAvail(4)
                }
        MAX-ACCESS  read-write
        STATUS  current
        DESCRIPTION
            "This object indicates the RS-232C mode when device has restarted."
        ::= { agentBasicConfig 4 }

    agentOutOfBandBaudRateConfig OBJECT-TYPE
        SYNTAX  INTEGER {
                    other(1),
                    baudRate-2400 (2),
                    baudRate-9600 (3),
                    baudRate-19200(4),
                    baudRate-38400(5),
                    baudRate-115200(6)
                }
        MAX-ACCESS  read-write
        STATUS  obsolete
        DESCRIPTION
            "This object allows user to specify out-of-band baud rate. It will take effect
			 when the system is restarted

			 Note:
			 Because these funictions will be limited by the system support, some of the
			 selected items will be invalid. Whenthe user selects one of the items,
			 it will respond with a bad-value status.
			 "
        ::= { agentBasicConfig 5 }

     agentSaveCfg OBJECT-TYPE
        SYNTAX INTEGER {
        			other(1),
        			idle(2),
        			set(3)
        		}
        MAX-ACCESS read-write
        STATUS current
        DESCRIPTION
            "As the object is set to 'set(3)', the current device configuration will be saved
             into to NV-RAM."
        ::= { agentBasicConfig 6 }

--***************************************************************************
--swMultiImageInfoTable
--***************************************************************************
    swMultiImageInfoTable OBJECT-TYPE
        SYNTAX  SEQUENCE OF SwMultiImageInfoEntry
        MAX-ACCESS  not-accessible
        STATUS  current
        DESCRIPTION
            ""
        ::= { agentBasicConfig 7 }

    swMultiImageInfoEntry OBJECT-TYPE
        SYNTAX  SwMultiImageInfoEntry
        MAX-ACCESS  not-accessible
        STATUS  current
        DESCRIPTION
            "A list of information about multiple image management."
        INDEX  { swMultiImageInfoID }
        ::= { swMultiImageInfoTable 1 }

    SwMultiImageInfoEntry ::=
        SEQUENCE {
        	swMultiImageInfoID
        		INTEGER,
            swMultiImageVersion
                DisplayString,
            swMultiImageSize
                Integer32,
            swMultiImageUpdateTime
                DisplayString,
            swMultiImageFrom
                DisplayString,
            swMultiImageSendUser
                DisplayString
        }
    swMultiImageInfoID OBJECT-TYPE
        SYNTAX  INTEGER
        MAX-ACCESS  read-only
        STATUS  current
        DESCRIPTION
            "The section ID of firmware image."
        ::= { swMultiImageInfoEntry 1 }

    swMultiImageVersion OBJECT-TYPE
        SYNTAX  DisplayString  (SIZE (0..32))
        MAX-ACCESS  read-only
        STATUS  current
        DESCRIPTION
            "The record of downloaded firmware version."
        ::= { swMultiImageInfoEntry 2 }

    swMultiImageSize OBJECT-TYPE
        SYNTAX  Integer32
        MAX-ACCESS  read-only
        STATUS  current
        DESCRIPTION
            "The record of downloaded firmware size."
        ::= { swMultiImageInfoEntry 3 }

    swMultiImageUpdateTime OBJECT-TYPE
        SYNTAX  DisplayString  (SIZE (0..32))
        MAX-ACCESS  read-only
        STATUS  current
        DESCRIPTION
            "The record of firmware updated time."
        ::= { swMultiImageInfoEntry 4 }

    swMultiImageFrom OBJECT-TYPE
        SYNTAX  DisplayString  (SIZE (0..32))
        MAX-ACCESS  read-only
        STATUS  current
        DESCRIPTION
            "The record of IP address of TFTP server."
        ::= { swMultiImageInfoEntry 5 }

    swMultiImageSendUser OBJECT-TYPE
        SYNTAX  DisplayString  (SIZE (0..32))
        MAX-ACCESS  read-only
        STATUS  current
        DESCRIPTION
            "The record of user who downloaded the firmware."
        ::= { swMultiImageInfoEntry 6 }

--***************************************************************************
--swMultiImageCtrlTable
--***************************************************************************
--    swMultiImageCtrlTable OBJECT-TYPE
--        SYNTAX  SEQUENCE OF SwMultiImageCtrlEntry
--        MAX-ACCESS  not-accessible
--        STATUS  current
--        DESCRIPTION
--            ""
--        ::= { agentBasicConfig 8 }

--    swMultiImageCtrlEntry OBJECT-TYPE
--        SYNTAX  SwMultiImageCtrlEntry
--        MAX-ACCESS  not-accessible
--        STATUS  current
--        DESCRIPTION
--            "A list of information about multiple image management."
--        INDEX  { swMultiImageID }
--        ::= { swMultiImageCtrlTable 1 }

--    SwMultiImageCtrlEntry ::=
--        SEQUENCE {
--        	swMultiImageCtrlID
--        		INTEGER,
--            swMultiImageSourceAddr
--                IpAddress,
--            swMultiImageFileName
--                DisplayString,
--            swMultiImageAction
--                INTEGER
--        }
--    swMultiImageCtrlID OBJECT-TYPE
--        SYNTAX  INTEGER
--        MAX-ACCESS  read-write
--        STATUS  current
--        DESCRIPTION
--            "The section ID of firmware image."
--        ::= { swMultiImageCtrlEntry 1 }

--    swMultiImageSourceAddr OBJECT-TYPE
--        SYNTAX  IpAddress
--        MAX-ACCESS  read-write
--        STATUS  current
--        DESCRIPTION
--            "The IP address where new firmware image file is located."
--        ::= { swMultiImageCtrlEntry 2 }

--    swMultiImageFileName OBJECT-TYPE
--        SYNTAX  DisplayString  (SIZE (0..64))
--        MAX-ACCESS  read-write
--        STATUS  current
--        DESCRIPTION
--            "The full name of the firmware image file to be downloaded."
--        ::= { swMultiImageCtrlEntry 3 }

--    swMultiImageAction OBJECT-TYPE
--		SYNTAX  INTEGER {
--               other(1),
--               update(2),
--               delete(3),
--               config-as-bootup-fw(4)
--               }
--        MAX-ACCESS  read-write
--        STATUS  current
--        DESCRIPTION
--            "This object indicates the status of multiImageTable actions.

--            other(1) - .
--            update(2) - download firmware to indicated section.
--            delete(3) - delete the firmware by indicated firmware ID.
--            config-as-bootup-fw(4) - configured as bootup firmware by indicated firmware(ID)."
--        ::= { swMultiImageCtrlEntry 4 }

--***************************************************************************
--agentTrustHostMgmt
--***************************************************************************

    agentTrustHostMgmt       OBJECT IDENTIFIER ::= { agentBasicConfig 10 }

    agentTrustHostTable OBJECT-TYPE
        SYNTAX  SEQUENCE OF AgentTrustHostEntry
        MAX-ACCESS  not-accessible
        STATUS  current
        DESCRIPTION
            "This table contains Trust Host information."
        ::= { agentTrustHostMgmt 1 }

    agentTrustHostEntry OBJECT-TYPE
        SYNTAX  AgentTrustHostEntry
        MAX-ACCESS  not-accessible
        STATUS  current
        DESCRIPTION
            "A list of information about Trust Host."
        INDEX  { agentTrustHostIndex }
        ::= { agentTrustHostTable 1 }

    AgentTrustHostEntry ::=
        SEQUENCE {
            agentTrustHostIndex
                INTEGER,
            agentTrustHostIPAddress
                IpAddress,
            agentTrustHostRowStatus
                RowStatus,
            agentTrustHostIPSubnetMask
                IpAddress
        }

    agentTrustHostIndex OBJECT-TYPE
        SYNTAX  INTEGER (1..10)
        MAX-ACCESS  read-only
        STATUS  current
        DESCRIPTION
            "The index of Trust Host entry."
        ::= { agentTrustHostEntry 1 }

    agentTrustHostIPAddress OBJECT-TYPE
        SYNTAX  IpAddress
        MAX-ACCESS  read-create
        STATUS  current
        DESCRIPTION
            "Specifies the IP address of the Trust Host."
        ::= { agentTrustHostEntry 2 }

    agentTrustHostRowStatus OBJECT-TYPE
        SYNTAX  RowStatus
        MAX-ACCESS  read-create
        STATUS  current
        DESCRIPTION
            "Indicates the status of this entry. When creating a Trust Host
             entry, the IP address should be set, too."
        ::= { agentTrustHostEntry 3 }

    agentTrustHostIPSubnetMask OBJECT-TYPE
        SYNTAX  IpAddress
        MAX-ACCESS  read-create
        STATUS  current
        DESCRIPTION
            "Specifies the IP subnet mask of the Trust Host."
        ::= { agentTrustHostEntry 4 }

--***************************************************************************
--agentFDBMgmt
--***************************************************************************

    agentFDBMgmt       OBJECT IDENTIFIER ::= { agentBasicConfig 11 }

    agentFDBClearAllState OBJECT-TYPE
        SYNTAX  INTEGER{
    		other(1),
    		start(2)
    		}
        MAX-ACCESS  read-write
        STATUS  current
        DESCRIPTION
            "Used to clear all FDB entries."
        ::= { agentFDBMgmt 1 }

--***************************************************************************
--agentARPMgmt
--***************************************************************************

    agentARPMgmt       OBJECT IDENTIFIER ::= { agentBasicConfig 12 }

    agentARPClearAllState OBJECT-TYPE
        SYNTAX  INTEGER{
    		other(1),
    		start(2)
    		}
        MAX-ACCESS  read-write
        STATUS  current
        DESCRIPTION
            "Used to clear all ARP entries."
        ::= { agentARPMgmt 1 }

-- -----------------------------------------------------------------------------
    agentReboot OBJECT-TYPE
        SYNTAX  INTEGER {
                    none(1),
                    start(2)
                }
        MAX-ACCESS  read-write
        STATUS      current
        DESCRIPTION
            "Used to restart the switch."
        ::= {  agentBasicConfig 19  }

    agentReset OBJECT-TYPE
        SYNTAX  INTEGER {
                    none(1),
                    config(2),
                    system(3),
					reset(4)
                }
        MAX-ACCESS  read-write
        STATUS      current
        DESCRIPTION
            "Used to reset all switch parameters.

			 none(1)  : No action. This is the default vaule of this object.
			 config(2): All parameters are reset to default	settings.
						But device will not do save neither reboot.
			 system(3): All parameters are reset to default	settings.
						Then the switch will do factory reset, save and	reboot.
			 reset(4) : All parameters will be reset to default settings except
						IP address, user account and history log.
						But device will not do save neither reboot.
			"
        ::= {  agentBasicConfig 20  }

--***************************************************************************
--agentTrustHostDelAllState
--***************************************************************************
    agentTrustHostDelAllState OBJECT-TYPE
        SYNTAX      INTEGER{
    		none(1),
    		start(2)
    		}
        MAX-ACCESS  read-write
        STATUS      current
        DESCRIPTION
            "Used to delete all Trust Host entries."
        ::= { agentTrustHostMgmt 2 }

    -- ***********************
    -- agentIpProtocolConfig *
    -- ***********************
    agentIpProtoConfig      OBJECT IDENTIFIER ::= { agentGeneralMgmt 3 }

    agentIpNumOfIf OBJECT-TYPE
        SYNTAX  Integer32
        MAX-ACCESS  read-only
        STATUS  current
        DESCRIPTION
            "The total number of IP interfaces supported by this agent."
        ::= {  agentIpProtoConfig 1 }

    agentIpTftpServerAddr OBJECT-TYPE
        SYNTAX  IpAddress
        MAX-ACCESS  read-write
        STATUS  obsolete
        DESCRIPTION
            "The IP Address of TFTP Server."
        ::= {  agentIpProtoConfig 2 }

    agentIpGetIpFrom OBJECT-TYPE
        SYNTAX  INTEGER {
                    other(1),
                    disabled(2),
                    bootp(3),
                    dhcp(4)
                }
        MAX-ACCESS  read-write
        STATUS  current
        DESCRIPTION
            "This object indicates whether the agent get its system IP address
             from Bootp/DHCP server at start up."
        ::= { agentIpProtoConfig 3 }

    agentIpAutoconfig OBJECT-TYPE
        SYNTAX  INTEGER {
                    enabled(1),
                    disabled(2)
                }
        MAX-ACCESS  read-write
        STATUS  current
        DESCRIPTION
            ""
        ::= { agentIpProtoConfig 4 }

	-- End of agentIpIfTable ---------

-- ******************************************************************************************
-- Add common trap management
-- ******************************************************************************************

	agentNotify	OBJECT IDENTIFIER ::= { agentGeneralMgmt 4 }

	agentNotifMgmt      OBJECT IDENTIFIER ::= { agentNotify 1 }

-- ******************************************************************************************
--	agentNotifMgmt
-- ******************************************************************************************

    systemTrapsSeverity OBJECT-TYPE
        SYNTAX  AgentNotifyLevel
        MAX-ACCESS  read-write
        STATUS  current
        DESCRIPTION
            "Indicates the level of system severity control. The system has a severity level control
            and each trap should be associated with a severity control. When a trap event occurs
            and its severity is higher than the system severity control level, the trap works
            as defined. If the event severity is lower than the system severity control level,
            the event is ignored as if it did not occur."
        ::= { agentNotifMgmt 1 }

    systemLogsSeverity OBJECT-TYPE
        SYNTAX  AgentNotifyLevel
        MAX-ACCESS  read-write
        STATUS  current
        DESCRIPTION
            "Indicates the level of system severity control. The system has a severity level control
            and each log should be associated with a severity control. When log event occurs
            and its severity is higher than the system severity control level, the log works
            as defined. If the event severity is lower than the system severity control level,
            the event is ignored as if it did not occur."
        ::= { agentNotifMgmt 2 }

    -- ************************
    -- agentIptrapMangerTable *
    -- ************************

--	agentIpTrapManager	OBJECT IDENTIFIER ::= { agentGeneralMgmt 4 }

--    agentIpTrapManagerTable OBJECT-TYPE-
--        SYNTAX  SEQUENCE OF AgentIpTrapManagerEntry
--        MAX-ACCESS  not-accessible
--        STATUS  current
--        DESCRIPTION
--            "A list of trap managers to which SNMP traps will be sent."
--        ::= {  agentIpTrapManager 1 }

--    agentIpTrapManagerEntry OBJECT-TYPE
--        SYNTAX  AgentIpTrapManagerEntry
--        MAX-ACCESS  not-accessible
--        STATUS  obsolete
--        DESCRIPTION
--            "Each entry contains the particular trap manager settings."
--        INDEX   { agentIpTrapManagerIpAddr }
--        ::= { agentIpTrapManagerTable 1 }

-- *****************************************************************************
--
-- *****************************************************************************

--    agentTrapManagerTable OBJECT-TYPE
--        SYNTAX  SEQUENCE OF AgentTrapManagerEntry
--        MAX-ACCESS  not-accessible
--        STATUS  current
--        DESCRIPTION
--            "A list of trap managers to which SNMP traps will be sent."
--        ::= {  agentIpTrapManager 2 }

--    agentTrapManagerEntry OBJECT-TYPE
--        SYNTAX  AgentTrapManagerEntry
--        MAX-ACCESS  not-accessible
--        STATUS  current
--        DESCRIPTION
--            "Each entry contains the particular trap manager settings."
--        INDEX   { agentTrapManagerIndex }
--        ::= { agentTrapManagerTable 1 }

--    AgentTrapManagerEntry ::=
--        SEQUENCE {
--				    agentTrapManagerIndex
--				        INTEGER,
--                    agentTrapManagerIpAddr
--                        IpAddress,
--                    agentTrapManagerComm
--                        DisplayString,
--                    agentTrapManagerMsgVer
--                        INTEGER,
--                    agentTrapManagerStatus
--                        INTEGER
--        }

--	agentTrapManagerIndex  OBJECT-TYPE
--	    SYNTAX     INTEGER (1..65535)
--	    MAX-ACCESS not-accessible
--	    STATUS     current
--	    DESCRIPTION
--	        "A value that uniquely identifies this trapDestEntry."
--	    ::= { agentTrapManagerEntry 1 }

--    agentTrapManagerIpAddr OBJECT-TYPE
--        SYNTAX  IpAddress
--        MAX-ACCESS  read-write
--        STATUS  current
--        DESCRIPTION
--            "The IP address where SNMP traps will be destined for"
--        ::= { agentTrapManagerEntry 2 }

--    agentTrapManagerComm OBJECT-TYPE
--        SYNTAX  DisplayString (SIZE (0..20))
--        MAX-ACCESS  read-write
--        STATUS  current
--        DESCRIPTION
--            "The community string used to encode SNMP trap packet to be sent to the trap
--             manager."
--        ::= { agentTrapManagerEntry 3 }

--    agentTrapManagerMsgVer OBJECT-TYPE
--        SYNTAX  INTEGER {
--                    snmpAgentVersionDependent(1),
--                    v1Trap(2),
--                    v2Trap(3)
--                }
--        MAX-ACCESS  read-write
--        STATUS  current
--        DESCRIPTION
--            "This object indicates the version of trap packets to be sent to
--             this trap manager. The default setting is SNMPAgentVersionDependent .

--			 Note:
--			 Because these funictions will be limited by the system support, some of the
--			 selected items will be invalid. When the user selects one of the items,
--                       it will respond with bad-value status."
--        ::= { agentTrapManagerEntry 4 }

--    agentTrapManagerStatus OBJECT-TYPE
--        SYNTAX  INTEGER {
--                    other(1),
--                    disabled(2),
--                    enabled(3)
--                }
--        MAX-ACCESS  read-write
--        STATUS  current
--        DESCRIPTION
--            "This object indicates whether or not the trap should be sent to
--             this trap manager."
--        ::= { agentTrapManagerEntry 5 }


--
-- Add for Slip_Console mode swtich 11-9-2001 WindChen
--
--	agentConsoleModeManager	OBJECT IDENTIFIER ::= { agentGeneralMgmt 5 }



--
-- Slip Mode Manager
--
--	agentSlipModeManager	OBJECT IDENTIFIER ::= { agentGeneralMgmt 6 }




-- ******************************************************************************************
-- Add common trap management
-- ******************************************************************************************


--	agentNotify	OBJECT IDENTIFIER ::= { agentGeneralMgmt 7 }



--	agentNotifMgmt      OBJECT IDENTIFIER ::= { agentNotify 1 }
--	agentNotifFirmware   OBJECT IDENTIFIER ::= { agentNotify 2 }



--	agentNotifyPrefix OBJECT IDENTIFIER ::= { agentNotifFirmware 0 }




-- ******************************************************************************************
--	agentNotifMgmt
-- ******************************************************************************************

--    systemTrapsSeverity OBJECT-TYPE
--        SYNTAX  AgentNotifyLevel
--        MAX-ACCESS  read-write
--        STATUS  current
--        DESCRIPTION
--            "Indicates the level of all system traps.
--			"
--        ::= { agentNotifMgmt 1 }

--	notifFirmwareMgmt OBJECT IDENTIFIER ::= { agentNotifMgmt 2 }

-- ******************************************************************************************

--    systemRestartTrapSeverity OBJECT-TYPE
--        SYNTAX  AgentNotifyLevel
--        MAX-ACCESS  read-write
--        STATUS  current
--        DESCRIPTION
--            "Indicates the level of the system restart detection.
--			"

--        ::= { notifFirmwareMgmt 1 }

--    saveToNVRAMTrapSeverity OBJECT-TYPE
--        SYNTAX  AgentNotifyLevel
--        MAX-ACCESS  read-write
--        STATUS  current
--        DESCRIPTION
--            "Indicates the level of SaveToNV-RAM detection.
--			"

--        ::= { notifFirmwareMgmt 2 }

--    fileTransferStatusChangeTrapSeverity OBJECT-TYPE
--        SYNTAX  AgentNotifyLevel
--        MAX-ACCESS  read-write
--        STATUS  current
--        DESCRIPTION
--            "Indicates the level of FileTransferStatusChange detection.
--			"

--        ::= { notifFirmwareMgmt 3 }


--    setToFactoryDefaultTrapSeverity OBJECT-TYPE
--        SYNTAX  AgentNotifyLevel
--        MAX-ACCESS  read-write
--        STATUS  current
--        DESCRIPTION
--            "Indicates the level of SetToFactoryDefault detection.
--			"

--        ::= { notifFirmwareMgmt 4 }



-- ******************************************************************************************

-- agentNotifFirmware OBJECT IDENTIFIER ::= { agentNotifyPrefix 0 }

-- ******************************************************************************************
--	agentNotifFirmware
-- ******************************************************************************************

--    agentsystemRestart NOTIFICATION-TYPE
--        OBJECTS {
--              trapInfosystemRestart
--        		}
--        STATUS  current
--        DESCRIPTION
--            " This trap contains the reboot informaton. "

--		::= { agentNotifyPrefix 1 }


--    agentSaveToNVRAM NOTIFICATION-TYPE
--        OBJECTS         { unitID
--                        }
--        STATUS  current
--        DESCRIPTION
--            "The trap is sent whenever save all configurations of device to NV-RAM has been processed . "

--        ::= { agentNotifyPrefix 2 }

--    agentFileTransferStatusChange NOTIFICATION-TYPE
--        OBJECTS         {
--        					unitID,
--                          agentStatusFileTransfer
--                        }
--        STATUS          current
--        DESCRIPTION     "File transfer status change notification."
--        ::= { agentNotifyPrefix 3 }

--    agentSetToFactoryDefault NOTIFICATION-TYPE
--        OBJECTS         { unitID
--                        }
--        STATUS  current
--        DESCRIPTION
--            "The trap is sent whenever the set to factory default setting has been processed . "

--        ::= { agentNotifyPrefix 4 }


-- ******************************************************************************************
--	agentNotifEquipment
-- ******************************************************************************************


-- ******************************************************************************************
--	notificationBidings
-- ******************************************************************************************

--    notificationBidings OBJECT IDENTIFIER ::= { agentNotifFirmware 1 }

--    unitID OBJECT-TYPE
--        SYNTAX     INTEGER
--        MAX-ACCESS accessible-for-notify
--        STATUS     current
--        DESCRIPTION
--            "The Unit ID of the device which triggered the event"
--        ::= { notificationBidings 1 }


--    trapInfosystemRestart   OBJECT-TYPE
--        SYNTAX  DisplayString (SIZE (0..64))
--        MAX-ACCESS  read-only
--        STATUS  current
--        DESCRIPTION
--            "This object indicates the time of the last reboot information.
--            "
--        ::= { notificationBidings 2 }


END
